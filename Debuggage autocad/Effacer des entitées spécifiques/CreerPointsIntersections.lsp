(defun c:CreerPointsIntersections ( / selset obj1 obj2 i j ptList intPoints)
  (prompt "\nSélectionnez des lignes, polylignes ou polylignes 3D : ")
  (setq selset (ssget '((0 . "LINE,LWPOLYLINE,POLYLINE"))))

  (if selset
    (progn
      (setq ptList '())
      (setq i 0)
      (while (< i (sslength selset))
        (setq obj1 (vlax-ename->vla-object (ssname selset i)))
        (setq j (1+ i))
        (while (< j (sslength selset))
          (setq obj2 (vlax-ename->vla-object (ssname selset j)))
          (setq intPoints (vlax-invoke obj1 'IntersectWith obj2 acExtendNone))
          (if intPoints
            (progn
              (setq k 0)
              (while (< k (length intPoints))
                (setq pt (list (nth k intPoints) (nth (+ 1 k) intPoints) (nth (+ 2 k) intPoints)))
                (entmakex (list (cons 0 "POINT") (cons 10 pt)))
                (setq ptList (cons pt ptList))
                (setq k (+ k 3))
              )
            )
          )
          (setq j (1+ j))
        )
        (setq i (1+ i))
      )
      (prompt (strcat "\nNombre de points d'intersection créés : " (itoa (length ptList))))
    )
    (prompt "\nAucun objet valide sélectionné.")
  )
  (princ)
)
